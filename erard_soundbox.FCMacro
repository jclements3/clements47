# FreeCAD macro - Erard Harp Soundbox
# 14.0" base to 4.0" neck, a=2b limacon, 9-pt cubic clamped soundboard curve
# Pins NOT forced to y=0; grommets derived from smooth curve.
# Regenerated by fix_soundbox.py
import FreeCAD, Part, math

doc = FreeCAD.newDocument('ErardHarp')
N_PTS = 60

sections = []

pts_0 = []
for j in range(N_PTS + 1):
    t = 2 * math.pi * j / N_PTS
    r = 4.666667 + 2.333333 * math.cos(t)
    u = r * math.cos(t)
    v = r * math.sin(t)
    pts_0.append(FreeCAD.Vector(10.000000 + u * (-0.826373), -59.648600 + u * (0.563123), v))
bsp_0 = Part.BSplineCurve()
bsp_0.interpolate(pts_0)
obj_0 = doc.addObject("Part::Feature", "Limacon_01")
obj_0.Shape = bsp_0.toShape()
sections.append(obj_0)

pts_1 = []
for j in range(N_PTS + 1):
    t = 2 * math.pi * j / N_PTS
    r = 4.618357 + 2.309179 * math.cos(t)
    u = r * math.cos(t)
    v = r * math.sin(t)
    pts_1.append(FreeCAD.Vector(10.524885 + u * (-0.833883), -58.866303 + u * (0.551941), v))
bsp_1 = Part.BSplineCurve()
bsp_1.interpolate(pts_1)
obj_1 = doc.addObject("Part::Feature", "Limacon_02")
obj_1.Shape = bsp_1.toShape()
sections.append(obj_1)

pts_2 = []
for j in range(N_PTS + 1):
    t = 2 * math.pi * j / N_PTS
    r = 4.570048 + 2.285024 * math.cos(t)
    u = r * math.cos(t)
    v = r * math.sin(t)
    pts_2.append(FreeCAD.Vector(11.041250 + u * (-0.838476), -58.078349 + u * (0.544939), v))
bsp_2 = Part.BSplineCurve()
bsp_2.interpolate(pts_2)
obj_2 = doc.addObject("Part::Feature", "Limacon_03")
obj_2.Shape = bsp_2.toShape()
sections.append(obj_2)

pts_3 = []
for j in range(N_PTS + 1):
    t = 2 * math.pi * j / N_PTS
    r = 4.521739 + 2.260870 * math.cos(t)
    u = r * math.cos(t)
    v = r * math.sin(t)
    pts_3.append(FreeCAD.Vector(11.552810 + u * (-0.840578), -57.287266 + u * (0.541691), v))
bsp_3 = Part.BSplineCurve()
bsp_3.interpolate(pts_3)
obj_3 = doc.addObject("Part::Feature", "Limacon_04")
obj_3.Shape = bsp_3.toShape()
sections.append(obj_3)

pts_4 = []
for j in range(N_PTS + 1):
    t = 2 * math.pi * j / N_PTS
    r = 4.473430 + 2.236715 * math.cos(t)
    u = r * math.cos(t)
    v = r * math.sin(t)
    pts_4.append(FreeCAD.Vector(12.062994 + u * (-0.840375), -56.495294 + u * (0.542005), v))
bsp_4 = Part.BSplineCurve()
bsp_4.interpolate(pts_4)
obj_4 = doc.addObject("Part::Feature", "Limacon_05")
obj_4.Shape = bsp_4.toShape()
sections.append(obj_4)

pts_5 = []
for j in range(N_PTS + 1):
    t = 2 * math.pi * j / N_PTS
    r = 4.425121 + 2.212560 * math.cos(t)
    u = r * math.cos(t)
    v = r * math.sin(t)
    pts_5.append(FreeCAD.Vector(12.575152 + u * (-0.837850), -55.704598 + u * (0.545900), v))
bsp_5 = Part.BSplineCurve()
bsp_5.interpolate(pts_5)
obj_5 = doc.addObject("Part::Feature", "Limacon_06")
obj_5.Shape = bsp_5.toShape()
sections.append(obj_5)

pts_6 = []
for j in range(N_PTS + 1):
    t = 2 * math.pi * j / N_PTS
    r = 4.376812 + 2.188406 * math.cos(t)
    u = r * math.cos(t)
    v = r * math.sin(t)
    pts_6.append(FreeCAD.Vector(13.092747 + u * (-0.832779), -54.917453 + u * (0.553605), v))
bsp_6 = Part.BSplineCurve()
bsp_6.interpolate(pts_6)
obj_6 = doc.addObject("Part::Feature", "Limacon_07")
obj_6.Shape = bsp_6.toShape()
sections.append(obj_6)

pts_7 = []
for j in range(N_PTS + 1):
    t = 2 * math.pi * j / N_PTS
    r = 4.328502 + 2.164251 * math.cos(t)
    u = r * math.cos(t)
    v = r * math.sin(t)
    pts_7.append(FreeCAD.Vector(13.619558 + u * (-0.824866), -54.136452 + u * (0.565328), v))
bsp_7 = Part.BSplineCurve()
bsp_7.interpolate(pts_7)
obj_7 = doc.addObject("Part::Feature", "Limacon_08")
obj_7.Shape = bsp_7.toShape()
sections.append(obj_7)

pts_8 = []
for j in range(N_PTS + 1):
    t = 2 * math.pi * j / N_PTS
    r = 4.280193 + 2.140097 * math.cos(t)
    u = r * math.cos(t)
    v = r * math.sin(t)
    pts_8.append(FreeCAD.Vector(14.154986 + u * (-0.822487), -53.361325 + u * (0.568784), v))
bsp_8 = Part.BSplineCurve()
bsp_8.interpolate(pts_8)
obj_8 = doc.addObject("Part::Feature", "Limacon_09")
obj_8.Shape = bsp_8.toShape()
sections.append(obj_8)

pts_9 = []
for j in range(N_PTS + 1):
    t = 2 * math.pi * j / N_PTS
    r = 4.231884 + 2.115942 * math.cos(t)
    u = r * math.cos(t)
    v = r * math.sin(t)
    pts_9.append(FreeCAD.Vector(14.686403 + u * (-0.830529), -52.583452 + u * (0.556975), v))
bsp_9 = Part.BSplineCurve()
bsp_9.interpolate(pts_9)
obj_9 = doc.addObject("Part::Feature", "Limacon_10")
obj_9.Shape = bsp_9.toShape()
sections.append(obj_9)

pts_10 = []
for j in range(N_PTS + 1):
    t = 2 * math.pi * j / N_PTS
    r = 4.183575 + 2.091787 * math.cos(t)
    u = r * math.cos(t)
    v = r * math.sin(t)
    pts_10.append(FreeCAD.Vector(15.200394 + u * (-0.846467), -51.793985 + u * (0.532442), v))
bsp_10 = Part.BSplineCurve()
bsp_10.interpolate(pts_10)
obj_10 = doc.addObject("Part::Feature", "Limacon_11")
obj_10.Shape = bsp_10.toShape()
sections.append(obj_10)

pts_11 = []
for j in range(N_PTS + 1):
    t = 2 * math.pi * j / N_PTS
    r = 4.135266 + 2.067633 * math.cos(t)
    u = r * math.cos(t)
    v = r * math.sin(t)
    pts_11.append(FreeCAD.Vector(15.687053 + u * (-0.866149), -50.987411 + u * (0.499785), v))
bsp_11 = Part.BSplineCurve()
bsp_11.interpolate(pts_11)
obj_11 = doc.addObject("Part::Feature", "Limacon_12")
obj_11.Shape = bsp_11.toShape()
sections.append(obj_11)

pts_12 = []
for j in range(N_PTS + 1):
    t = 2 * math.pi * j / N_PTS
    r = 4.086957 + 2.043478 * math.cos(t)
    u = r * math.cos(t)
    v = r * math.sin(t)
    pts_12.append(FreeCAD.Vector(16.141020 + u * (-0.885963), -50.162005 + u * (0.463757), v))
bsp_12 = Part.BSplineCurve()
bsp_12.interpolate(pts_12)
obj_12 = doc.addObject("Part::Feature", "Limacon_13")
obj_12.Shape = bsp_12.toShape()
sections.append(obj_12)

pts_13 = []
for j in range(N_PTS + 1):
    t = 2 * math.pi * j / N_PTS
    r = 4.038647 + 2.019324 * math.cos(t)
    u = r * math.cos(t)
    v = r * math.sin(t)
    pts_13.append(FreeCAD.Vector(16.560922 + u * (-0.903810), -49.318755 + u * (0.427934), v))
bsp_13 = Part.BSplineCurve()
bsp_13.interpolate(pts_13)
obj_13 = doc.addObject("Part::Feature", "Limacon_14")
obj_13.Shape = bsp_13.toShape()
sections.append(obj_13)

pts_14 = []
for j in range(N_PTS + 1):
    t = 2 * math.pi * j / N_PTS
    r = 3.990338 + 1.995169 * math.cos(t)
    u = r * math.cos(t)
    v = r * math.sin(t)
    pts_14.append(FreeCAD.Vector(16.948046 + u * (-0.918935), -48.459953 + u * (0.394409), v))
bsp_14 = Part.BSplineCurve()
bsp_14.interpolate(pts_14)
obj_14 = doc.addObject("Part::Feature", "Limacon_15")
obj_14.Shape = bsp_14.toShape()
sections.append(obj_14)

pts_15 = []
for j in range(N_PTS + 1):
    t = 2 * math.pi * j / N_PTS
    r = 3.942029 + 1.971014 * math.cos(t)
    u = r * math.cos(t)
    v = r * math.sin(t)
    pts_15.append(FreeCAD.Vector(17.305062 + u * (-0.931363), -47.588191 + u * (0.364092), v))
bsp_15 = Part.BSplineCurve()
bsp_15.interpolate(pts_15)
obj_15 = doc.addObject("Part::Feature", "Limacon_16")
obj_15.Shape = bsp_15.toShape()
sections.append(obj_15)

pts_16 = []
for j in range(N_PTS + 1):
    t = 2 * math.pi * j / N_PTS
    r = 3.893720 + 1.946860 * math.cos(t)
    u = r * math.cos(t)
    v = r * math.sin(t)
    pts_16.append(FreeCAD.Vector(17.635122 + u * (-0.941443), -46.705860 + u * (0.337172), v))
bsp_16 = Part.BSplineCurve()
bsp_16.interpolate(pts_16)
obj_16 = doc.addObject("Part::Feature", "Limacon_17")
obj_16.Shape = bsp_16.toShape()
sections.append(obj_16)

pts_17 = []
for j in range(N_PTS + 1):
    t = 2 * math.pi * j / N_PTS
    r = 3.845411 + 1.922705 * math.cos(t)
    u = r * math.cos(t)
    v = r * math.sin(t)
    pts_17.append(FreeCAD.Vector(17.941477 + u * (-0.949387), -45.815013 + u * (0.314109), v))
bsp_17 = Part.BSplineCurve()
bsp_17.interpolate(pts_17)
obj_17 = doc.addObject("Part::Feature", "Limacon_18")
obj_17.Shape = bsp_17.toShape()
sections.append(obj_17)

pts_18 = []
for j in range(N_PTS + 1):
    t = 2 * math.pi * j / N_PTS
    r = 3.797101 + 1.898551 * math.cos(t)
    u = r * math.cos(t)
    v = r * math.sin(t)
    pts_18.append(FreeCAD.Vector(18.228752 + u * (-0.955011), -44.917820 + u * (0.296571), v))
bsp_18 = Part.BSplineCurve()
bsp_18.interpolate(pts_18)
obj_18 = doc.addObject("Part::Feature", "Limacon_19")
obj_18.Shape = bsp_18.toShape()
sections.append(obj_18)

pts_19 = []
for j in range(N_PTS + 1):
    t = 2 * math.pi * j / N_PTS
    r = 3.748792 + 1.874396 * math.cos(t)
    u = r * math.cos(t)
    v = r * math.sin(t)
    pts_19.append(FreeCAD.Vector(18.501524 + u * (-0.959097), -44.016105 + u * (0.283077), v))
bsp_19 = Part.BSplineCurve()
bsp_19.interpolate(pts_19)
obj_19 = doc.addObject("Part::Feature", "Limacon_20")
obj_19.Shape = bsp_19.toShape()
sections.append(obj_19)

pts_20 = []
for j in range(N_PTS + 1):
    t = 2 * math.pi * j / N_PTS
    r = 3.700483 + 1.850242 * math.cos(t)
    u = r * math.cos(t)
    v = r * math.sin(t)
    pts_20.append(FreeCAD.Vector(18.763021 + u * (-0.962159), -43.111055 + u * (0.272489), v))
bsp_20 = Part.BSplineCurve()
bsp_20.interpolate(pts_20)
obj_20 = doc.addObject("Part::Feature", "Limacon_21")
obj_20.Shape = bsp_20.toShape()
sections.append(obj_20)

pts_21 = []
for j in range(N_PTS + 1):
    t = 2 * math.pi * j / N_PTS
    r = 3.652174 + 1.826087 * math.cos(t)
    u = r * math.cos(t)
    v = r * math.sin(t)
    pts_21.append(FreeCAD.Vector(19.015618 + u * (-0.964499), -42.203477 + u * (0.264086), v))
bsp_21 = Part.BSplineCurve()
bsp_21.interpolate(pts_21)
obj_21 = doc.addObject("Part::Feature", "Limacon_22")
obj_21.Shape = bsp_21.toShape()
sections.append(obj_21)

pts_22 = []
for j in range(N_PTS + 1):
    t = 2 * math.pi * j / N_PTS
    r = 3.603865 + 1.801932 * math.cos(t)
    u = r * math.cos(t)
    v = r * math.sin(t)
    pts_22.append(FreeCAD.Vector(19.261135 + u * (-0.966306), -41.293958 + u * (0.257395), v))
bsp_22 = Part.BSplineCurve()
bsp_22.interpolate(pts_22)
obj_22 = doc.addObject("Part::Feature", "Limacon_23")
obj_22.Shape = bsp_22.toShape()
sections.append(obj_22)

pts_23 = []
for j in range(N_PTS + 1):
    t = 2 * math.pi * j / N_PTS
    r = 3.555556 + 1.777778 * math.cos(t)
    u = r * math.cos(t)
    v = r * math.sin(t)
    pts_23.append(FreeCAD.Vector(19.501023 + u * (-0.967704), -40.382936 + u * (0.252090), v))
bsp_23 = Part.BSplineCurve()
bsp_23.interpolate(pts_23)
obj_23 = doc.addObject("Part::Feature", "Limacon_24")
obj_23.Shape = bsp_23.toShape()
sections.append(obj_23)

pts_24 = []
for j in range(N_PTS + 1):
    t = 2 * math.pi * j / N_PTS
    r = 3.507246 + 1.753623 * math.cos(t)
    u = r * math.cos(t)
    v = r * math.sin(t)
    pts_24.append(FreeCAD.Vector(19.736475 + u * (-0.968774), -39.470758 + u * (0.247945), v))
bsp_24 = Part.BSplineCurve()
bsp_24.interpolate(pts_24)
obj_24 = doc.addObject("Part::Feature", "Limacon_25")
obj_24.Shape = bsp_24.toShape()
sections.append(obj_24)

pts_25 = []
for j in range(N_PTS + 1):
    t = 2 * math.pi * j / N_PTS
    r = 3.458937 + 1.729469 * math.cos(t)
    u = r * math.cos(t)
    v = r * math.sin(t)
    pts_25.append(FreeCAD.Vector(19.968504 + u * (-0.969573), -38.557703 + u * (0.244802), v))
bsp_25 = Part.BSplineCurve()
bsp_25.interpolate(pts_25)
obj_25 = doc.addObject("Part::Feature", "Limacon_26")
obj_25.Shape = bsp_25.toShape()
sections.append(obj_25)

pts_26 = []
for j in range(N_PTS + 1):
    t = 2 * math.pi * j / N_PTS
    r = 3.410628 + 1.705314 * math.cos(t)
    u = r * math.cos(t)
    v = r * math.sin(t)
    pts_26.append(FreeCAD.Vector(20.197999 + u * (-0.970139), -37.644007 + u * (0.242549), v))
bsp_26 = Part.BSplineCurve()
bsp_26.interpolate(pts_26)
obj_26 = doc.addObject("Part::Feature", "Limacon_27")
obj_26.Shape = bsp_26.toShape()
sections.append(obj_26)

pts_27 = []
for j in range(N_PTS + 1):
    t = 2 * math.pi * j / N_PTS
    r = 3.362319 + 1.681159 * math.cos(t)
    u = r * math.cos(t)
    v = r * math.sin(t)
    pts_27.append(FreeCAD.Vector(20.425759 + u * (-0.970498), -36.729878 + u * (0.241111), v))
bsp_27 = Part.BSplineCurve()
bsp_27.interpolate(pts_27)
obj_27 = doc.addObject("Part::Feature", "Limacon_28")
obj_27.Shape = bsp_27.toShape()
sections.append(obj_27)

pts_28 = []
for j in range(N_PTS + 1):
    t = 2 * math.pi * j / N_PTS
    r = 3.314010 + 1.657005 * math.cos(t)
    u = r * math.cos(t)
    v = r * math.sin(t)
    pts_28.append(FreeCAD.Vector(20.652529 + u * (-0.970663), -35.815502 + u * (0.240442), v))
bsp_28 = Part.BSplineCurve()
bsp_28.interpolate(pts_28)
obj_28 = doc.addObject("Part::Feature", "Limacon_29")
obj_28.Shape = bsp_28.toShape()
sections.append(obj_28)

pts_29 = []
for j in range(N_PTS + 1):
    t = 2 * math.pi * j / N_PTS
    r = 3.265700 + 1.632850 * math.cos(t)
    u = r * math.cos(t)
    v = r * math.sin(t)
    pts_29.append(FreeCAD.Vector(20.879024 + u * (-0.970643), -34.901058 + u * (0.240523), v))
bsp_29 = Part.BSplineCurve()
bsp_29.interpolate(pts_29)
obj_29 = doc.addObject("Part::Feature", "Limacon_30")
obj_29.Shape = bsp_29.toShape()
sections.append(obj_29)

pts_30 = []
for j in range(N_PTS + 1):
    t = 2 * math.pi * j / N_PTS
    r = 3.217391 + 1.608696 * math.cos(t)
    u = r * math.cos(t)
    v = r * math.sin(t)
    pts_30.append(FreeCAD.Vector(21.105947 + u * (-0.970437), -33.986720 + u * (0.241355), v))
bsp_30 = Part.BSplineCurve()
bsp_30.interpolate(pts_30)
obj_30 = doc.addObject("Part::Feature", "Limacon_31")
obj_30.Shape = bsp_30.toShape()
sections.append(obj_30)

pts_31 = []
for j in range(N_PTS + 1):
    t = 2 * math.pi * j / N_PTS
    r = 3.169082 + 1.584541 * math.cos(t)
    u = r * math.cos(t)
    v = r * math.sin(t)
    pts_31.append(FreeCAD.Vector(21.334017 + u * (-0.970035), -33.072668 + u * (0.242964), v))
bsp_31 = Part.BSplineCurve()
bsp_31.interpolate(pts_31)
obj_31 = doc.addObject("Part::Feature", "Limacon_32")
obj_31.Shape = bsp_31.toShape()
sections.append(obj_31)

pts_32 = []
for j in range(N_PTS + 1):
    t = 2 * math.pi * j / N_PTS
    r = 3.120773 + 1.560386 * math.cos(t)
    u = r * math.cos(t)
    v = r * math.sin(t)
    pts_32.append(FreeCAD.Vector(21.563988 + u * (-0.969421), -32.159092 + u * (0.245402), v))
bsp_32 = Part.BSplineCurve()
bsp_32.interpolate(pts_32)
obj_32 = doc.addObject("Part::Feature", "Limacon_33")
obj_32.Shape = bsp_32.toShape()
sections.append(obj_32)

pts_33 = []
for j in range(N_PTS + 1):
    t = 2 * math.pi * j / N_PTS
    r = 3.072464 + 1.536232 * math.cos(t)
    u = r * math.cos(t)
    v = r * math.sin(t)
    pts_33.append(FreeCAD.Vector(21.796677 + u * (-0.968568), -31.246205 + u * (0.248751), v))
bsp_33 = Part.BSplineCurve()
bsp_33.interpolate(pts_33)
obj_33 = doc.addObject("Part::Feature", "Limacon_34")
obj_33.Shape = bsp_33.toShape()
sections.append(obj_33)

pts_34 = []
for j in range(N_PTS + 1):
    t = 2 * math.pi * j / N_PTS
    r = 3.024155 + 1.512077 * math.cos(t)
    u = r * math.cos(t)
    v = r * math.sin(t)
    pts_34.append(FreeCAD.Vector(22.032887 + u * (-0.967527), -30.334223 + u * (0.252769), v))
bsp_34 = Part.BSplineCurve()
bsp_34.interpolate(pts_34)
obj_34 = doc.addObject("Part::Feature", "Limacon_35")
obj_34.Shape = bsp_34.toShape()
sections.append(obj_34)

pts_35 = []
for j in range(N_PTS + 1):
    t = 2 * math.pi * j / N_PTS
    r = 2.975845 + 1.487923 * math.cos(t)
    u = r * math.cos(t)
    v = r * math.sin(t)
    pts_35.append(FreeCAD.Vector(22.273037 + u * (-0.966379), -29.423271 + u * (0.257122), v))
bsp_35 = Part.BSplineCurve()
bsp_35.interpolate(pts_35)
obj_35 = doc.addObject("Part::Feature", "Limacon_36")
obj_35.Shape = bsp_35.toShape()
sections.append(obj_35)

pts_36 = []
for j in range(N_PTS + 1):
    t = 2 * math.pi * j / N_PTS
    r = 2.927536 + 1.463768 * math.cos(t)
    u = r * math.cos(t)
    v = r * math.sin(t)
    pts_36.append(FreeCAD.Vector(22.517463 + u * (-0.965108), -28.513456 + u * (0.261851), v))
bsp_36 = Part.BSplineCurve()
bsp_36.interpolate(pts_36)
obj_36 = doc.addObject("Part::Feature", "Limacon_37")
obj_36.Shape = bsp_36.toShape()
sections.append(obj_36)

pts_37 = []
for j in range(N_PTS + 1):
    t = 2 * math.pi * j / N_PTS
    r = 2.879227 + 1.439614 * math.cos(t)
    u = r * math.cos(t)
    v = r * math.sin(t)
    pts_37.append(FreeCAD.Vector(22.766538 + u * (-0.963695), -27.604905 + u * (0.267005), v))
bsp_37 = Part.BSplineCurve()
bsp_37.interpolate(pts_37)
obj_37 = doc.addObject("Part::Feature", "Limacon_38")
obj_37.Shape = bsp_37.toShape()
sections.append(obj_37)

pts_38 = []
for j in range(N_PTS + 1):
    t = 2 * math.pi * j / N_PTS
    r = 2.830918 + 1.415459 * math.cos(t)
    u = r * math.cos(t)
    v = r * math.sin(t)
    pts_38.append(FreeCAD.Vector(23.020692 + u * (-0.962116), -26.697760 + u * (0.272640), v))
bsp_38 = Part.BSplineCurve()
bsp_38.interpolate(pts_38)
obj_38 = doc.addObject("Part::Feature", "Limacon_39")
obj_38.Shape = bsp_38.toShape()
sections.append(obj_38)

pts_39 = []
for j in range(N_PTS + 1):
    t = 2 * math.pi * j / N_PTS
    r = 2.782609 + 1.391304 * math.cos(t)
    u = r * math.cos(t)
    v = r * math.sin(t)
    pts_39.append(FreeCAD.Vector(23.280407 + u * (-0.960342), -25.792192 + u * (0.278826), v))
bsp_39 = Part.BSplineCurve()
bsp_39.interpolate(pts_39)
obj_39 = doc.addObject("Part::Feature", "Limacon_40")
obj_39.Shape = bsp_39.toShape()
sections.append(obj_39)

pts_40 = []
for j in range(N_PTS + 1):
    t = 2 * math.pi * j / N_PTS
    r = 2.734300 + 1.367150 * math.cos(t)
    u = r * math.cos(t)
    v = r * math.sin(t)
    pts_40.append(FreeCAD.Vector(23.546242 + u * (-0.958334), -24.888403 + u * (0.285649), v))
bsp_40 = Part.BSplineCurve()
bsp_40.interpolate(pts_40)
obj_40 = doc.addObject("Part::Feature", "Limacon_41")
obj_40.Shape = bsp_40.toShape()
sections.append(obj_40)

pts_41 = []
for j in range(N_PTS + 1):
    t = 2 * math.pi * j / N_PTS
    r = 2.685990 + 1.342995 * math.cos(t)
    u = r * math.cos(t)
    v = r * math.sin(t)
    pts_41.append(FreeCAD.Vector(23.818844 + u * (-0.956048), -23.986632 + u * (0.293210), v))
bsp_41 = Part.BSplineCurve()
bsp_41.interpolate(pts_41)
obj_41 = doc.addObject("Part::Feature", "Limacon_42")
obj_41.Shape = bsp_41.toShape()
sections.append(obj_41)

pts_42 = []
for j in range(N_PTS + 1):
    t = 2 * math.pi * j / N_PTS
    r = 2.637681 + 1.318841 * math.cos(t)
    u = r * math.cos(t)
    v = r * math.sin(t)
    pts_42.append(FreeCAD.Vector(24.098967 + u * (-0.953422), -23.087170 + u * (0.301640), v))
bsp_42 = Part.BSplineCurve()
bsp_42.interpolate(pts_42)
obj_42 = doc.addObject("Part::Feature", "Limacon_43")
obj_42.Shape = bsp_42.toShape()
sections.append(obj_42)

pts_43 = []
for j in range(N_PTS + 1):
    t = 2 * math.pi * j / N_PTS
    r = 2.589372 + 1.294686 * math.cos(t)
    u = r * math.cos(t)
    v = r * math.sin(t)
    pts_43.append(FreeCAD.Vector(24.387503 + u * (-0.950377), -22.190370 + u * (0.311101), v))
bsp_43 = Part.BSplineCurve()
bsp_43.interpolate(pts_43)
obj_43 = doc.addObject("Part::Feature", "Limacon_44")
obj_43.Shape = bsp_43.toShape()
sections.append(obj_43)

pts_44 = []
for j in range(N_PTS + 1):
    t = 2 * math.pi * j / N_PTS
    r = 2.541063 + 1.270531 * math.cos(t)
    u = r * math.cos(t)
    v = r * math.sin(t)
    pts_44.append(FreeCAD.Vector(24.685518 + u * (-0.946807), -21.296679 + u * (0.321802), v))
bsp_44 = Part.BSplineCurve()
bsp_44.interpolate(pts_44)
obj_44 = doc.addObject("Part::Feature", "Limacon_45")
obj_44.Shape = bsp_44.toShape()
sections.append(obj_44)

pts_45 = []
for j in range(N_PTS + 1):
    t = 2 * math.pi * j / N_PTS
    r = 2.492754 + 1.246377 * math.cos(t)
    u = r * math.cos(t)
    v = r * math.sin(t)
    pts_45.append(FreeCAD.Vector(24.994301 + u * (-0.942567), -20.406652 + u * (0.334016), v))
bsp_45 = Part.BSplineCurve()
bsp_45.interpolate(pts_45)
obj_45 = doc.addObject("Part::Feature", "Limacon_46")
obj_45.Shape = bsp_45.toShape()
sections.append(obj_45)

pts_46 = []
for j in range(N_PTS + 1):
    t = 2 * math.pi * j / N_PTS
    r = 2.444444 + 1.222222 * math.cos(t)
    u = r * math.cos(t)
    v = r * math.sin(t)
    pts_46.append(FreeCAD.Vector(25.315442 + u * (-0.937456), -19.521011 + u * (0.348104), v))
bsp_46 = Part.BSplineCurve()
bsp_46.interpolate(pts_46)
obj_46 = doc.addObject("Part::Feature", "Limacon_47")
obj_46.Shape = bsp_46.toShape()
sections.append(obj_46)

pts_47 = []
for j in range(N_PTS + 1):
    t = 2 * math.pi * j / N_PTS
    r = 2.396135 + 1.198068 * math.cos(t)
    u = r * math.cos(t)
    v = r * math.sin(t)
    pts_47.append(FreeCAD.Vector(25.650892 + u * (-0.931260), -18.640694 + u * (0.364355), v))
bsp_47 = Part.BSplineCurve()
bsp_47.interpolate(pts_47)
obj_47 = doc.addObject("Part::Feature", "Limacon_48")
obj_47.Shape = bsp_47.toShape()
sections.append(obj_47)

pts_48 = []
for j in range(N_PTS + 1):
    t = 2 * math.pi * j / N_PTS
    r = 2.347826 + 1.173913 * math.cos(t)
    u = r * math.cos(t)
    v = r * math.sin(t)
    pts_48.append(FreeCAD.Vector(26.002351 + u * (-0.924167), -17.766649 + u * (0.381988), v))
bsp_48 = Part.BSplineCurve()
bsp_48.interpolate(pts_48)
obj_48 = doc.addObject("Part::Feature", "Limacon_49")
obj_48.Shape = bsp_48.toShape()
sections.append(obj_48)

pts_49 = []
for j in range(N_PTS + 1):
    t = 2 * math.pi * j / N_PTS
    r = 2.299517 + 1.149758 * math.cos(t)
    u = r * math.cos(t)
    v = r * math.sin(t)
    pts_49.append(FreeCAD.Vector(26.371000 + u * (-0.916147), -16.899714 + u * (0.400842), v))
bsp_49 = Part.BSplineCurve()
bsp_49.interpolate(pts_49)
obj_49 = doc.addObject("Part::Feature", "Limacon_50")
obj_49.Shape = bsp_49.toShape()
sections.append(obj_49)

pts_50 = []
for j in range(N_PTS + 1):
    t = 2 * math.pi * j / N_PTS
    r = 2.251208 + 1.125604 * math.cos(t)
    u = r * math.cos(t)
    v = r * math.sin(t)
    pts_50.append(FreeCAD.Vector(26.757961 + u * (-0.907132), -16.040800 + u * (0.420846), v))
bsp_50 = Part.BSplineCurve()
bsp_50.interpolate(pts_50)
obj_50 = doc.addObject("Part::Feature", "Limacon_51")
obj_50.Shape = bsp_50.toShape()
sections.append(obj_50)

pts_51 = []
for j in range(N_PTS + 1):
    t = 2 * math.pi * j / N_PTS
    r = 2.202899 + 1.101449 * math.cos(t)
    u = r * math.cos(t)
    v = r * math.sin(t)
    pts_51.append(FreeCAD.Vector(27.164248 + u * (-0.897097), -15.190859 + u * (0.441834), v))
bsp_51 = Part.BSplineCurve()
bsp_51.interpolate(pts_51)
obj_51 = doc.addObject("Part::Feature", "Limacon_52")
obj_51.Shape = bsp_51.toShape()
sections.append(obj_51)

pts_52 = []
for j in range(N_PTS + 1):
    t = 2 * math.pi * j / N_PTS
    r = 2.154589 + 1.077295 * math.cos(t)
    u = r * math.cos(t)
    v = r * math.sin(t)
    pts_52.append(FreeCAD.Vector(27.590662 + u * (-0.886092), -14.350839 + u * (0.463510), v))
bsp_52 = Part.BSplineCurve()
bsp_52.interpolate(pts_52)
obj_52 = doc.addObject("Part::Feature", "Limacon_53")
obj_52.Shape = bsp_52.toShape()
sections.append(obj_52)

pts_53 = []
for j in range(N_PTS + 1):
    t = 2 * math.pi * j / N_PTS
    r = 2.106280 + 1.053140 * math.cos(t)
    u = r * math.cos(t)
    v = r * math.sin(t)
    pts_53.append(FreeCAD.Vector(28.037643 + u * (-0.874289), -13.521580 + u * (0.485406), v))
bsp_53 = Part.BSplineCurve()
bsp_53.interpolate(pts_53)
obj_53 = doc.addObject("Part::Feature", "Limacon_54")
obj_53.Shape = bsp_53.toShape()
sections.append(obj_53)

pts_54 = []
for j in range(N_PTS + 1):
    t = 2 * math.pi * j / N_PTS
    r = 2.057971 + 1.028986 * math.cos(t)
    u = r * math.cos(t)
    v = r * math.sin(t)
    pts_54.append(FreeCAD.Vector(28.505103 + u * (-0.862028), -12.703691 + u * (0.506860), v))
bsp_54 = Part.BSplineCurve()
bsp_54.interpolate(pts_54)
obj_54 = doc.addObject("Part::Feature", "Limacon_55")
obj_54.Shape = bsp_54.toShape()
sections.append(obj_54)

pts_55 = []
for j in range(N_PTS + 1):
    t = 2 * math.pi * j / N_PTS
    r = 2.009662 + 1.004831 * math.cos(t)
    u = r * math.cos(t)
    v = r * math.sin(t)
    pts_55.append(FreeCAD.Vector(28.992238 + u * (-0.849848), -11.897362 + u * (0.527028), v))
bsp_55 = Part.BSplineCurve()
bsp_55.interpolate(pts_55)
obj_55 = doc.addObject("Part::Feature", "Limacon_56")
obj_55.Shape = bsp_55.toShape()
sections.append(obj_55)

pts_56 = []
for j in range(N_PTS + 1):
    t = 2 * math.pi * j / N_PTS
    r = 1.961353 + 0.980676 * math.cos(t)
    u = r * math.cos(t)
    v = r * math.sin(t)
    pts_56.append(FreeCAD.Vector(29.498063 + u * (-0.837146), -11.102625 + u * (0.546979), v))
bsp_56 = Part.BSplineCurve()
bsp_56.interpolate(pts_56)
obj_56 = doc.addObject("Part::Feature", "Limacon_57")
obj_56.Shape = bsp_56.toShape()
sections.append(obj_56)

pts_57 = []
for j in range(N_PTS + 1):
    t = 2 * math.pi * j / N_PTS
    r = 1.913043 + 0.956522 * math.cos(t)
    u = r * math.cos(t)
    v = r * math.sin(t)
    pts_57.append(FreeCAD.Vector(30.023116 + u * (-0.823140), -10.320461 + u * (0.567838), v))
bsp_57 = Part.BSplineCurve()
bsp_57.interpolate(pts_57)
obj_57 = doc.addObject("Part::Feature", "Limacon_58")
obj_57.Shape = bsp_57.toShape()
sections.append(obj_57)

pts_58 = []
for j in range(N_PTS + 1):
    t = 2 * math.pi * j / N_PTS
    r = 1.864734 + 0.932367 * math.cos(t)
    u = r * math.cos(t)
    v = r * math.sin(t)
    pts_58.append(FreeCAD.Vector(30.568211 + u * (-0.807763), -9.552134 + u * (0.589507), v))
bsp_58 = Part.BSplineCurve()
bsp_58.interpolate(pts_58)
obj_58 = doc.addObject("Part::Feature", "Limacon_59")
obj_58.Shape = bsp_58.toShape()
sections.append(obj_58)

pts_59 = []
for j in range(N_PTS + 1):
    t = 2 * math.pi * j / N_PTS
    r = 1.816425 + 0.908213 * math.cos(t)
    u = r * math.cos(t)
    v = r * math.sin(t)
    pts_59.append(FreeCAD.Vector(31.134044 + u * (-0.790985), -8.798953 + u * (0.611835), v))
bsp_59 = Part.BSplineCurve()
bsp_59.interpolate(pts_59)
obj_59 = doc.addObject("Part::Feature", "Limacon_60")
obj_59.Shape = bsp_59.toShape()
sections.append(obj_59)

pts_60 = []
for j in range(N_PTS + 1):
    t = 2 * math.pi * j / N_PTS
    r = 1.768116 + 0.884058 * math.cos(t)
    u = r * math.cos(t)
    v = r * math.sin(t)
    pts_60.append(FreeCAD.Vector(31.721142 + u * (-0.772833), -8.062230 + u * (0.634609), v))
bsp_60 = Part.BSplineCurve()
bsp_60.interpolate(pts_60)
obj_60 = doc.addObject("Part::Feature", "Limacon_61")
obj_60.Shape = bsp_60.toShape()
sections.append(obj_60)

pts_61 = []
for j in range(N_PTS + 1):
    t = 2 * math.pi * j / N_PTS
    r = 1.719807 + 0.859903 * math.cos(t)
    u = r * math.cos(t)
    v = r * math.sin(t)
    pts_61.append(FreeCAD.Vector(32.329797 + u * (-0.753397), -7.343216 + u * (0.657566), v))
bsp_61 = Part.BSplineCurve()
bsp_61.interpolate(pts_61)
obj_61 = doc.addObject("Part::Feature", "Limacon_62")
obj_61.Shape = bsp_61.toShape()
sections.append(obj_61)

pts_62 = []
for j in range(N_PTS + 1):
    t = 2 * math.pi * j / N_PTS
    r = 1.671498 + 0.835749 * math.cos(t)
    u = r * math.cos(t)
    v = r * math.sin(t)
    pts_62.append(FreeCAD.Vector(32.960348 + u * (-0.732043), -6.643332 + u * (0.681258), v))
bsp_62 = Part.BSplineCurve()
bsp_62.interpolate(pts_62)
obj_62 = doc.addObject("Part::Feature", "Limacon_63")
obj_62.Shape = bsp_62.toShape()
sections.append(obj_62)

pts_63 = []
for j in range(N_PTS + 1):
    t = 2 * math.pi * j / N_PTS
    r = 1.623188 + 0.811594 * math.cos(t)
    u = r * math.cos(t)
    v = r * math.sin(t)
    pts_63.append(FreeCAD.Vector(33.613722 + u * (-0.708210), -5.964714 + u * (0.706002), v))
bsp_63 = Part.BSplineCurve()
bsp_63.interpolate(pts_63)
obj_63 = doc.addObject("Part::Feature", "Limacon_64")
obj_63.Shape = bsp_63.toShape()
sections.append(obj_63)

pts_64 = []
for j in range(N_PTS + 1):
    t = 2 * math.pi * j / N_PTS
    r = 1.574879 + 0.787440 * math.cos(t)
    u = r * math.cos(t)
    v = r * math.sin(t)
    pts_64.append(FreeCAD.Vector(34.290855 + u * (-0.681655), -5.309812 + u * (0.731674), v))
bsp_64 = Part.BSplineCurve()
bsp_64.interpolate(pts_64)
obj_64 = doc.addObject("Part::Feature", "Limacon_65")
obj_64.Shape = bsp_64.toShape()
sections.append(obj_64)

pts_65 = []
for j in range(N_PTS + 1):
    t = 2 * math.pi * j / N_PTS
    r = 1.526570 + 0.763285 * math.cos(t)
    u = r * math.cos(t)
    v = r * math.sin(t)
    pts_65.append(FreeCAD.Vector(34.992540 + u * (-0.652155), -4.681297 + u * (0.758085), v))
bsp_65 = Part.BSplineCurve()
bsp_65.interpolate(pts_65)
obj_65 = doc.addObject("Part::Feature", "Limacon_66")
obj_65.Shape = bsp_65.toShape()
sections.append(obj_65)

pts_66 = []
for j in range(N_PTS + 1):
    t = 2 * math.pi * j / N_PTS
    r = 1.478261 + 0.739130 * math.cos(t)
    u = r * math.cos(t)
    v = r * math.sin(t)
    pts_66.append(FreeCAD.Vector(35.719188 + u * (-0.620905), -4.081827 + u * (0.783886), v))
bsp_66 = Part.BSplineCurve()
bsp_66.interpolate(pts_66)
obj_66 = doc.addObject("Part::Feature", "Limacon_67")
obj_66.Shape = bsp_66.toShape()
sections.append(obj_66)

pts_67 = []
for j in range(N_PTS + 1):
    t = 2 * math.pi * j / N_PTS
    r = 1.429952 + 0.714976 * math.cos(t)
    u = r * math.cos(t)
    v = r * math.sin(t)
    pts_67.append(FreeCAD.Vector(36.466712 + u * (-0.598153), -3.508543 + u * (0.801382), v))
bsp_67 = Part.BSplineCurve()
bsp_67.interpolate(pts_67)
obj_67 = doc.addObject("Part::Feature", "Limacon_68")
obj_67.Shape = bsp_67.toShape()
sections.append(obj_67)

pts_68 = []
for j in range(N_PTS + 1):
    t = 2 * math.pi * j / N_PTS
    r = 1.381643 + 0.690821 * math.cos(t)
    u = r * math.cos(t)
    v = r * math.sin(t)
    pts_68.append(FreeCAD.Vector(37.225755 + u * (-0.588899), -2.950555 + u * (0.808206), v))
bsp_68 = Part.BSplineCurve()
bsp_68.interpolate(pts_68)
obj_68 = doc.addObject("Part::Feature", "Limacon_69")
obj_68.Shape = bsp_68.toShape()
sections.append(obj_68)

pts_69 = []
for j in range(N_PTS + 1):
    t = 2 * math.pi * j / N_PTS
    r = 1.333333 + 0.666667 * math.cos(t)
    u = r * math.cos(t)
    v = r * math.sin(t)
    pts_69.append(FreeCAD.Vector(37.986000 + u * (-0.594736), -2.394200 + u * (0.803921), v))
bsp_69 = Part.BSplineCurve()
bsp_69.interpolate(pts_69)
obj_69 = doc.addObject("Part::Feature", "Limacon_70")
obj_69.Shape = bsp_69.toShape()
sections.append(obj_69)

loft = doc.addObject('Part::Loft', 'Soundbox')
loft.Sections = sections
loft.Solid = True
loft.Ruled = False
loft.Closed = False

doc.recompute()
